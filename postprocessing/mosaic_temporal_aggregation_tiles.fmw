FME workspace mosaic_temporal_aggregation_tiles.fmw

Parameters:
- SourceDataset_GEOTIFF = C:\Temp\tsmodel\1km\local\martens2_1k_global_fixhr\monthly_synoptic_combined_pf\tiles\*.tif   # Source GeoTIFF File(s)
- DestDataset_GEOTIFF = C:\Temp\tsmodel\1km\local\martens2_1k_global_fixhr\monthly_synoptic_combined_pf   # Destination GeoTIFF Folder

Readers:
- GEOTIFF_1: GEOTIFF from $(SourceDataset_GEOTIFF)

Writers:
- GEOTIFF_2: GEOTIFF to $(DestDataset_GEOTIFF)

GEOTIFF (reader GEOTIFF_1)
    -> AttributeSplitter
AttributeSplitter
    DROP_EMPTY_PARTS = No
    DELIMITER = .
    TRIM_OPTION = Both
    ATTR_NAME = fme_basename
    LIST_NAME = _list
    -> ListIndexer
ListIndexer
    PREFIX = _mth
    INDEX = 1
    LIST_ATTR = _list{}
    -> ListIndexer_2
ListIndexer_2
    PREFIX = _stat
    INDEX = 2
    LIST_ATTR = _list{}
    -> AttributeCreator
AttributeCreator
    ATTR_TABLE = SET_TO _out = TSI-Martens2-Pf.@Value(_mth_list).@Value(_stat_list).1km
    -> RasterMosaicker
RasterMosaicker
    ACCUM_ATTRS_NAME = Use Attributes From One Feature
    GROUP_BY = _out
    MERGE_PALETTES_NAME = Yes
    SNAPPING_TYPE_NAME = Resample
    NODATA_OVERWRITE = No
    INTERPOLATION_TYPE_NAME = Nearest Neighbor
    OVERLAPPING_VALUES = last
    -> GEOTIFF (writer GEOTIFF_2)
GEOTIFF (writer GEOTIFF_2)
