FME workspace merge_output_tiles.fmw

Parameters:
- SourceDataset_GEOTIFF = E:\Data\Harry\Documents\dial-a-map\tsi_update_e8\v6\-10W-42E--4N--36S-2000px_tiles\*.tif   # Source GeoTIFF File(s)
- FEATURE_TYPES =
- DestDataset_GEOTIFF = E:\Data\Harry\Documents\dial-a-map\tsi_update_e8\v6   # Destination GeoTIFF Folder
- out_tag = 1km_e8_pf_martens2   # tag for filename (suffix after the date)

Readers:
- GEOTIFF_1: GEOTIFF from $(SourceDataset_GEOTIFF)

Writers:
- GEOTIFF_2: GEOTIFF to $(DestDataset_GEOTIFF)

GEOTIFF (reader GEOTIFF_1)
    -> Tester
Tester
    TEST_CLAUSE = TEST @Value(fme_dataset) CONTAINS tiles
    TEST_MODE = Automatic
    BOOL_OP = OR
    TEST_DESCRIPTION = ""
    PASSED -> StringSearcher
StringSearcher
    CASE = no
    MATCHED_RESULT_ATTR = _date
    REGEXP = \d{4}\.\d{2}
    STRING_TO_SEARCH = @Value(fme_basename)
    MATCHED -> RasterMosaicker
RasterMosaicker
    COMPOSITE_USING_ALPHA_BAND_NAME = No
    NODATA_OVERWRITE = No
    SNAPPING_TYPE_NAME = Offset
    MERGE_PALETTES_NAME = Yes
    INTERPOLATION_TYPE_NAME = Nearest Neighbor
    GROUP_BY = _date
    ACCUM_ATTRS_NAME = Get Attributes From One Representative Feature
    -> AttributeCreator
AttributeCreator
    ATTR_TABLE = SET_TO _outname = @Value(_date)_$(out_tag)
    -> GEOTIFF (writer GEOTIFF_2)
GEOTIFF (writer GEOTIFF_2)
