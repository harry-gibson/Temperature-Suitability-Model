FME workspace mosaic_different_models.fmw

Parameters:
- SourceDataset_GEOTIFF_3 = C:\Temp\tsmodel\5km\local\martens2_5k_global_fixhr\mosaic_62day\TSI-Martens2-62day.*.5km.tif   # Source GeoTIFF File(s)
- SourceDataset_ESRISHAPE = C:\Temp\tsmodel\5km\local\martens2_5k_global_fixhr\lifespan_62day_area_5k.shp   # Source Esri Shapefile(s)
- SourceDataset_GEOTIFF = C:\Temp\tsmodel\5km\local\martens2_5k_global_fixhr\mosaic\TSI-Martens2.*.5km.tif   # Source GeoTIFF File(s)
- DestDataset_GEOTIFF = C:\Temp\tsmodel\5km\local\martens2_5k_global_fixhr\mosaic_62day_comb   # Destination GeoTIFF Folder

Readers:
- GEOTIFF_1: GEOTIFF from $(SourceDataset_GEOTIFF)
- GEOTIFF_2: GEOTIFF from $(SourceDataset_GEOTIFF_3)
- ESRISHAPE_1: ESRISHAPE from $(SourceDataset_ESRISHAPE)

Writers:
- GEOTIFF_3: GEOTIFF to $(DestDataset_GEOTIFF)

lifespan_62day_area_5k (reader ESRISHAPE_1)
    attributes: OBJECTID long, Id long, gridcode long
    -> Clipper [CLIPPER]
GEOTIFF (reader GEOTIFF_2)
    -> StringSearcher_2
StringSearcher_2
    STRING_TO_SEARCH = @Value(fme_basename)
    REGEXP = \d{4}\.\d{2}
    CASE = no
    MATCHED_RESULT_ATTR = _datestr
    MATCHED -> Clipper [CLIPPEE]
Clipper
    CLIP_TYPE = Multiple Clippers
    DEFAULT_VAL = 0
    VAL_SOURCE = Clippee Only
    CONNECT_Z_MODE = First Wins
    LINES_AS_SEGMENTS = No
    PRESERVE_CLIPPEE_EXTENTS = No
    CLIPPED_ATTR = _clipped
    MEASURE_TYPE = Continuous
    ATTR_ACCUM_MODE = Merge Clipper
    BOUNDARY_CASES = Treat as Inside
    MISSING_VAL_MODE = Compute
    CREATE_AGGREGATES = Yes
    ATTR_CONFLICT_RES = Use Clippee
    INSIDE -> RasterMosaicker
GEOTIFF (reader GEOTIFF_1)
    -> StringSearcher
StringSearcher
    STRING_TO_SEARCH = @Value(fme_basename)
    REGEXP = \d{4}\.\d{2}
    CASE = no
    MATCHED_RESULT_ATTR = _datestr
    MATCHED -> RasterMosaicker
RasterMosaicker
    SNAPPING_TYPE_NAME = Resample
    GROUP_BY = _datestr
    MERGE_PALETTES_NAME = Yes
    ACCUM_ATTRS_NAME = Use Attributes From One Feature
    INTERPOLATION_TYPE_NAME = Nearest Neighbor
    NODATA_OVERWRITE = No
    OVERLAPPING_VALUES = last
    -> AttributeCreator
AttributeCreator
    ATTR_TABLE = SET_TO _outname = TSI-Martens2.@Value(_datestr).5km.Comb
    -> GEOTIFF (writer GEOTIFF_3)
GEOTIFF (writer GEOTIFF_3)
