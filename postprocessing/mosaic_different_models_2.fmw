FME workspace mosaic_different_models_2.fmw

Parameters:
- SourceDataset_GEOTIFF = C:\Temp\tsmodel\5km\local\martens2_5k_global_fixhr\mosaic_62day_pv\*.tif   # Source GeoTIFF File(s)
- SourceDataset_GEOTIFF_3 = C:\Temp\tsmodel\5km\local\martens2_5k_global_fixhr\mosaic_31day_pv\*.tif   # Source GeoTIFF File(s)
- DestDataset_GEOTIFF = C:\Temp\tsmodel\5km\local\martens2_5k_global_fixhr\mosaic_pv_combined   # Destination GeoTIFF Folder
- SourceDataset_ESRISHAPE = C:\Temp\tsmodel\5km\local\martens2_5k_global_fixhr\lifespan_62day_area_5k.shp   # Source Esri Shapefile(s)

Readers:
- GEOTIFF_2: GEOTIFF from $(SourceDataset_GEOTIFF_3)
- GEOTIFF_1: GEOTIFF from $(SourceDataset_GEOTIFF)
- ESRISHAPE_1: ESRISHAPE from $(SourceDataset_ESRISHAPE)

Writers:
- GEOTIFF_3: GEOTIFF to $(DestDataset_GEOTIFF)

lifespan_62day_area_5k (reader ESRISHAPE_1)
    attributes: OBJECTID long, Id long, gridcode long
    -> Sampler
Sampler
    SAMPLE_TYPE_LONG = First N Features
    RATE = 1
    SAMPLE_MODE = No
    SAMPLED -> Clipper [CLIPPER]
GEOTIFF (reader GEOTIFF_1)
    -> StringSearcher_2
StringSearcher_2
    CASE = no
    REGEXP = \d{4}.\d{2}
    MATCHED_RESULT_ATTR = _first_match
    STRING_TO_SEARCH = @Value(fme_basename)
    MATCHED -> Clipper [CLIPPEE]
Clipper
    MEASURE_TYPE = Continuous
    LINES_AS_SEGMENTS = No
    BOUNDARY_CASES = Treat as Inside
    VAL_SOURCE = Clippee Only
    CREATE_AGGREGATES = Yes
    PRESERVE_CLIPPEE_EXTENTS = No
    CLIPPED_ATTR = _clipped
    MISSING_VAL_MODE = Compute
    CLIP_TYPE = Multiple Clippers
    INSIDE -> RasterMosaicker
GEOTIFF (reader GEOTIFF_2)
    -> StringSearcher
StringSearcher
    CASE = no
    REGEXP = \d{4}.\d{2}
    MATCHED_RESULT_ATTR = _first_match
    STRING_TO_SEARCH = @Value(fme_basename)
    MATCHED -> RasterMosaicker
RasterMosaicker
    MERGE_PALETTES_NAME = Yes
    SNAPPING_TYPE_NAME = Resample
    ACCUM_ATTRS_NAME = Use Attributes From One Feature
    GROUP_BY = _first_match
    NODATA_OVERWRITE = No
    INTERPOLATION_TYPE_NAME = Nearest Neighbor
    OVERLAPPING_VALUES = last
    -> AttributeCreator
AttributeCreator
    ATTR_TABLE = SET_TO _outname = TSI-Martens2-Pv.@Value(_first_match).5km
    -> GEOTIFF (writer GEOTIFF_3)
GEOTIFF (writer GEOTIFF_3)
